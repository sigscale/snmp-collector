CT-TRAP-MIB DEFINITIONS ::= BEGIN

IMPORTS
	MODULE-IDENTITY, NOTIFICATION-TYPE, enterprises
		FROM SNMPv2-SMI
	NOTIFICATION-GROUP
		FROM SNMPv2-CONF
	sysContact, sysName, sysLocation
		FROM SNMPv2-MIB;


ctTrapModule MODULE-IDENTITY
		LAST-UPDATED "201808130000Z"
		ORGANIZATION "SigScale Global Inc."
		CONTACT-INFO
			"SigScale Global Inc.
			 716/1/3 Dr. Danister de Silva Mawatha
			 Colombo 00900
			 Sri Lanka
			 Tel: +94771231660
			 E-mail: support@sigscale.org"
		DESCRIPTION
			"Test MIB for TRAPs in snmp_collector application"
	::= { sigscaleExperiment 5051 }

sigscale OBJECT IDENTIFIER ::= { enterprises 50386 }
sigscaleExperiment OBJECT IDENTIFIER ::= { sigscale 5 }
ctTrapMib OBJECT IDENTIFIER ::= { ctTrapModule 1 } 
ctTrapConformance OBJECT IDENTIFIER ::= { ctTrapMib 1 }

ctTrap1 NOTIFICATION-TYPE
		OBJECTS  {
			sysContact,
			sysName,
			sysLocation
			}
		STATUS  current
		DESCRIPTION
			"This event is sent when a SNMP trap is
			being tested."
	::= { ctTrapMib 2 }

ctTrapMIBGroups OBJECT IDENTIFIER ::= { ctTrapConformance 1 }

ctTrapMIBGroup NOTIFICATION-GROUP
	NOTIFICATIONS { ctTrap1 }
	STATUS current
	DESCRIPTION 
		"This is a generated notification from sigscale."
	::= { ctTrapMIBGroups 1 }

END
